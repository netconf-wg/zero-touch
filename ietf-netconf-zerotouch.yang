module ietf-netconf-zerotouch {

  namespace "urn:ietf:params:xml:ns:yang:ietf-netconf-zerotouch";
  prefix "zerotouch";

  organization
   "IETF NETCONF (Network Configuration) Working Group";

  contact
   "WG Web:   <http://tools.ietf.org/wg/netconf/>
    WG List:  <mailto:netconf@ietf.org>

    WG Chair: Mehmet Ersue
              <mailto:mehmet.ersue@nsn.com>

    WG Chair: Bert Wijnen
              <mailto:bertietf@bwijnen.net>

    Editor:   Kent Watsen
              <mailto:kwatsen@juniper.net>";

  description
   "This module contains a collection of YANG definitions for
    configuring NETCONF zerotouch.

    Copyright (c) 2014 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";
  // RFC Ed.: replace XXXX with actual RFC number and
  // remove this note

  // RFC Ed.: please update the date to the date of publication

  revision "2014-07-01" {
    description
     "Initial version";
    reference
     "RFC XXXX: A YANG Data Model for NETCONF ZeroTouch Configlet";
  }

  container configlet {
    description
     "Top-level container for ZeroTouch configuration objects.";

    container target-requirements {
      description 
        "Specifies requirements for device this is loaded onto";
      leaf unique-identifier {
        type string;
        mandatory true;
        description
          "The device MUST have this unique identifier.  The value
           MUST be the same as the 'subject' field in the device's
           DevID credential, as specified by section 7.2.8 in
           IEEE Std 802.1AR-2009.";
      }
      leaf software-version {
        type string;
        mandatory true;
        description
          "The device MUST must be running this version of software.
           The value for this field is device-specific, but it MUST
           be an exact match (e.g., 14.1R2.5)";
      }
    }
    anyxml configuration {
        mandatory true; 
        description 
          "The configuration to be committed to the device's running
           datastore.  The configuration MUST be valid for the target
           device.  Devices supporting ZeroTouch SHOULD 
           support the following standard data-models:

             ietf-system          // the authentication container
             ietf-netconf-server  // the call-home container
           
           These three data models contain everything needed to
           support NETCONF call home using either SSH or TLS.";
        reference
          "RFC 7317: A YABF Data Model for System Management
           RFC YYYY: NETCONF Server Configuration Model";
    }
  }

}
